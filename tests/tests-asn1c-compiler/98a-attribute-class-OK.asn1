-- OK: Everything is fine

-- iso.org.dod.internet.private.enterprise (1.3.6.1.4.1)
-- .spelio.software.asn1c.test (9363.1.5.1)
-- .98

ModuleAttributeClass
	{ iso org(3) dod(6) internet (1) private(4) enterprise(1)
		spelio(9363) software(1) asn1c(5) test(1) 98 1 }
	DEFINITIONS ::=
BEGIN

	ATTRIBUTE ::= CLASS {
		&id RELATIVE-OID UNIQUE,
		&power INTEGER,
		&nametag IA5String
	} WITH SYNTAX { ID &id, POWER &power, NAME TAG &nametag}

	Attribute ::= SEQUENCE {
		identifier ATTRIBUTE.&id ({Attributes}),
		siAttributeValue IA5String
	}

-- Create an Object Set of concrete instances of ATTRIBUTE Class
-- 3 of them reference the values below, the last is defined inline
	Attributes ATTRIBUTE ::= { rafService | rcfService | rdfService | { ID {3 2 4}, POWER 50, NAME TAG "nameref"}}

	rafService ATTRIBUTE ::= { ID raf, POWER 10, NAME TAG "nameraf"}
	rcfService ATTRIBUTE ::= { ID rcf, POWER 20, NAME TAG "namercf"}
	rdfService ATTRIBUTE ::= { ID {3 2 3}, POWER 30, NAME TAG "namerdf"}


	raf RELATIVE-OID ::= {3 2 1}
	rcf RELATIVE-OID ::= {3 2 2}

END
