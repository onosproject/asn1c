-- OK: Everything is fine

-- iso.org.dod.internet.private.enterprise (1.3.6.1.4.1)
-- .spelio.software.asn1c.test (9363.1.5.1)
-- .13 1
-- .13 2

ModuleTestResolver1
	{ iso org(3) dod(6) internet(1) private(4) enterprise(1)
		spelio(9363) software(1) asn1c(5) test(1) 13 1 }
	DEFINITIONS ::=
BEGIN
	IMPORTS IntegerType, beta FROM
		ModuleTestResolver2
		{ iso org(3) dod(6) internet(1) private(4) enterprise(1)
			spelio(9363) software(1) asn1c(5) test(1) 13 2 };

	-- external reference
	alpha IntegerType ::= beta
	alpha2 ModuleTestResolver2.IntegerType ::= beta

	-- 
	-- The following are for post-fix checking by the check_fixer.
	-- It will be able to pick-up these values if the file is parseable,
	-- even if it contains some semantic errors.
	-- 

	check-alpha INTEGER ::= 123
	check-alpha2 INTEGER ::= 123

END

ModuleTestResolver2
	{ iso org(3) dod(6) internet(1) private(4) enterprise(1)
		spelio(9363) software(1) asn1c(5) test(1) 13 2 }
	DEFINITIONS ::=
BEGIN
	EXPORTS beta, IntegerType ;

	beta HiddenType ::= 123

	HiddenType ::= INTEGER

	IntegerType ::= INTEGER

END
